module czechlight-roadm-v2 {

  namespace
    "http://czechlight.cesnet.cz/netconf/roadm/v2";

  prefix "czechlight-roadm-v2";

  import czechlight-optical-channels {
    prefix "chan";
    revision-date 2017-07-04;
  }

  organization "CESNET";
  contact "photonic@cesnet.cz";
  description "CL-ROADMv2";

  revision 2017-07-04 {
    description "Channel frequencies are back in THz";
  }

  revision 2017-05-23 {
    description "HACK: pass frequency in GHz using integers";
  }

  revision 2017-05-22 {
    description "Access to current alarm state";
  }

  revision 2017-05-16 {
    description "Notifications about channel power at the INPUT port";
  }

  revision 2017-05-15 {
    description "Consistent property naming";
  }

  revision 2017-05-02 {
    description "Initial release";
  }

  typedef pass-mode {
    type enumeration {
      enum ADD {
        description "The INPUT signal goes to DROP, and the signal from the ADD port goes to OUTPUT.";
      }
      enum DROP {
        description "The INPUT signal is available on a DROP. Nothing is routed to OUTPUT.";
      }
      enum PASS {
        description "Channel is routed from the INPUT to the OUTPUT port; a small part is available on the DROP as well.";
      }
    }
  }

  typedef attenuation {
    type decimal64 {
      fraction-digits 1;
      range "0.0..25.5";
    }
    units "dB";
  }

  typedef measured-power {
    type decimal64 {
      fraction-digits 2;
    }
    units "dBm";
  }

  typedef power-hysteresis {
    type decimal64 {
      fraction-digits 2;
      range "0.0..10.0";
    }
    units "dBm";
  }

  grouping channel-threshold {
    leaf critical-level {
      type measured-power;
      mandatory true;
      description "Any power smaller than this one is considered to be a serious problem.";
    }

    leaf critical-hysteresis {
      type power-hysteresis;
      default 1.0;
      description "Hysteresis for critical-level";
    }
  }

  container roadm {
    description "A 40-channel fixed-grid 100 GHz Reconfigurable Optical Add-Drop Multiplexer";

    container channel-plan {
      list channel {
        must "channel-width = 100.0" {
          error-message "Channel bandwidth must be 100 GHz";
        }
        must "center-frequency >= 192.0" {
          error-message "Channels below 192.000 THz (C-band ITU channel 20) are not supported";
        }
        must "center-frequency <= 195.9" {
          error-message "Channels above 195.900 THz (C-band ITU channel 59) are not supported";
        }
        must "center-frequency * 10 = round(center-frequency * 10)" {
          error-message "Channel is not aligned to a 100 GHz fixed grid";
        }
        must "count(/roadm/channel-plan/channel[
          (center-frequency < current()/center-frequency) and
          (center-frequency * 1000 + (channel-width div 2) > current()/center-frequency * 1000 - (current()/channel-width div 2))
          ]) = 0" {
          error-message "Another channel with a lower frequency overlaps with this one";
        }
        key "center-frequency";
        uses chan:optical-channel;
        min-elements 40;
        max-elements 40;
        description "List of supported DWDM channels -- a subset of the 100 GHz ITU fixed grid,
        channels 20 to 59 (192.000 THz to 195.900 THz)";
      }
    }

    container configuration {
      list channel {
        key "center-frequency";

        leaf center-frequency {
          type leafref {
            path "../../../channel-plan/channel/center-frequency";
          }
        }

        leaf mode {
          type pass-mode;
          mandatory true;
          description "How to route the optical signal between the INPUT, ADD and OUTPUT ports";
        }

        leaf voa-attenuation {
          when "../mode = 'ADD' or ../mode = 'PASS'";
          type attenuation;
          mandatory true;
          description "Attenuation of the VOA in dB";
        }

        leaf description {
          type string;
          description "Free-text description. Can be used to add a local remark by an administrator
          about the purpose or destination of this channel, etc.";
        }

        container min-level-input {
          presence true;
          uses channel-threshold;
          description "Alarm configuration for power at the INPUT port";
        }
      }
    }

    container optical-power {
      config false;

      list channel {
        key "center-frequency";

        leaf center-frequency {
          type leafref {
            path "../../../channel-plan/channel/center-frequency";
          }
        }

        leaf input {
          type measured-power;
          mandatory true;
          description "Channel power at the INPUT port";
        }

        leaf drop {
          type measured-power;
          mandatory true;
          description "Channel power at the DROP port";
        }

        leaf output {
          type measured-power;
          mandatory true;
          description "Channel power at the OUTPUT port";
        }

        leaf input-signal-lost {
          type boolean;
          mandatory true;
          description "Is the signal at the INPUT port outside of the configured range?";
        }
      }
    }

    container aggregate-power {
      config false;

      leaf input {
        type measured-power;
        mandatory true;
        description "Total aggrgeate power at the INPUT port";
      }

      leaf output {
        type measured-power;
        mandatory true;
        description "Total aggrgeate power at the OUTPUT port";
      }
    }

  }

  notification input-signal-lost {
    description "Signal on a specified channel has been lost at the INPUT port";
    leaf center-frequency {
      type leafref {
        path "/roadm/channel-plan/channel/center-frequency";
      }
      mandatory true;
    }
  }

  notification input-signal-restored {
    description "The INPUT port detects incoming signal at the specified channel again";
    leaf center-frequency {
      type leafref {
        path "/roadm/channel-plan/channel/center-frequency";
      }
      mandatory true;
    }
  }

}
